submodule test-include-module {
    // namespace "urn:include-module";
    // prefix incl;

	belongs-to "test-module" {
		prefix "test";
	}


    // organization
    //   "organization info.";

    // contact
    //   "neoul@ymail.com";

    // description
    //   "The module description for included YANG.";

    // revision 2016-08-16 {
    //   description
    //     "revision description";
    //   reference
    //     "0.0.1";
    // }

    container included-top {
    	description
    		"This is top module";
    	list listnode {
    		key "akey";
    		description
    			"List nodes of the included-top";
    	
    		leaf akey {
    			type string;
    			description
    				"The key of the listnode";
    		}

    		leaf aleaf {
    			type string;
    			description
    				"The leaf of the listnode";
    		}
    	}
    }
}
