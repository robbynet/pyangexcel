module test-import-module {

    namespace "urn:test-import-module";
    prefix imp;

    organization
      "imported organization";

    contact
      "neoul@ymail.com";

    description
      "imported module";

    revision 2016-08-16 {
      description
        "Revision description";
      reference
        "0.0.1";
    }

    container importedcontainer {
    	description
    		"Top container of imported-module";
    	leaf importedcontainerleaf {
    		type string;
    		description
    			"imported container leaf.";
    	}
    }

    grouping agroup {
    	container abc {
	    	leaf apa {
    			type string;
    			description
    				"apa leaf";
 		   	}	
	    	leaf snorp {
    			type string;
    			description
    				"snorp node";
 		   	}	
		}
    }
}
